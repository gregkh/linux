--
-- This is the unencrypted variant
--
PrivateKeyInfo ::= SEQUENCE {
	version			Version,
	privateKeyAlgorithm	PrivateKeyAlgorithmIdentifier,
	privateKey		PrivateKey,
	attributes		[0] IMPLICIT Attributes OPTIONAL
}

Version ::= INTEGER  ({ pkcs8_note_version })

PrivateKeyAlgorithmIdentifier ::= AlgorithmIdentifier ({ pkcs8_note_algo })

PrivateKey ::= OCTET STRING ({ pkcs8_note_key })

Attributes ::= SET OF Attribute

Attribute ::= ANY

AlgorithmIdentifier ::= SEQUENCE {
	algorithm   OBJECT IDENTIFIER ({ pkcs8_note_OID }),
	parameters  ANY OPTIONAL ({ pkcs8_note_algo_parameter })
}
